"""Build the Rev8 alternative and export its geometry and artwork."""
import runpy
from pathlib import Path
runpy.run_path(str(Path(__file__).resolve().with_name('build_enclosure.py')), run_name='__main__')
